module sdnfirewall-impl {
    yang-version 1;
    namespace "urn:opendaylight:params:xml:ns:yang:sdnfirewall:impl";
    prefix "sdnfirewall-impl";

    import config { prefix config; revision-date 2013-04-05; }
    import opendaylight-md-sal-binding { prefix md-sal-binding; revision-date 2013-10-28;}

    description
        "Service definition for sdnfirewall project";

    revision "2014-12-10" {
        description
            "Initial revision";
    }

    identity sdnfirewall {
        base config:module-type;
        config:java-name-prefix Sdnfirewall;
    }

    augment "/config:modules/config:module/config:configuration" {
        case sdnfirewall {
            when "/config:modules/config:module/config:type = 'sdnfirewall'";
            container broker {
                uses config:service-ref {
                    refine type {
                        mandatory true;
                        config:required-identity md-sal-binding:binding-broker-osgi-registry;
                    }
                }
            }
        }
    }
}
